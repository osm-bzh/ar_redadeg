FME workspace traitements_phase_3_decoupage.fmw

Parameters:
- DestDataset_GEOJSON =
- DestDataset_GEOJSON_4 =
- DestDataset_GEOJSON_5 =
- DestDataset_POSTGIS =
- FME_USER_PARAM_PRIVATE_GRP =
- START =
- SourceDataset_POSTGIS =
- SourceDataset_POSTGRES =
- postgres_sql_where_clause =
- secteur_id =

Readers:
- POSTGRES_1: POSTGRES from $(SourceDataset_POSTGRES)
- POSTGIS_1: POSTGIS from $(SourceDataset_POSTGIS)

Writers:
- POSTGIS_2: POSTGIS to $(DestDataset_POSTGIS) in EPSG:2154
- GEOJSON_1: GEOJSON to $(DestDataset_GEOJSON) in EPSG:4326
- GEOJSON_2: GEOJSON to $(DestDataset_GEOJSON_5) in EPSG:4326
- GEOJSON_3: GEOJSON to $(DestDataset_GEOJSON_4) in EPSG:4326

Note: public.phase_2_trace_pgr
phase_2_trace_pgr (reader POSTGIS_1) [off]
    attributes: secteur_id int4, path_seq int8, node int8, cost float8, agg_cost float8, osm_id int8, highway text, type text, oneway text, ref text, name_fr text, name_br text
    -> Sorter_5
    -> BulkAttributeRenamer_2
Sorter_5
    SORT_PARM = path_seq NUMERIC ASCENDING
    SORTED -> AttributeKeeper_2
AttributeKeeper_2
    CREATE_BULK_MODE_FEATURES = NO
    KEEP_ATTRS = secteur_id
    -> LineCombiner
Note: on fait 1 seule ligne par secteur. / Logiquement vu que ça se suit ça fait une belle ligne continue
LineCombiner
    ACCUM_ATTRS_NAME = Use Attributes From One Feature
    BREAK = no
    BREAK_CONNECTION_ACROSS_SETS = No
    BREAK_CONNECTION_ATTRIBUTES = secteur_id
    CONNECT_Z_MODE = Ignore
    CONSIDER_NODE_ELEVATION = no
    DEAGGREGATE_GEOMETRY = Deaggregate
    LINES_AS_SEGMENTS = No
    PRESERVE = no
    TOPOLOGY = End noded
    LINE -> FeatureMerger_2 [REQUESTOR]
BulkAttributeRenamer_2
    ATTRCHOICE = All Attributes
    MODE_CHOICE = RENAME
    PATTERN_ACTION_DISP = ADDPREFIX
    REPLACE_STR = way_
    -> PointOnLineOverlayer [LINE]
SQLCreator
    COORDSYS = EPSG:2154
    DATASET = bed110@redadeg_2021@redadeg
    EXPOSED_ATTRIBUTE_LIST = vertex secteur_id
    FORMAT = POSTGIS
    POSTGIS_NAMED_CONNECTION = bed110@redadeg_2021@redadeg
    SQL_STATEMENT:
      SELECT vertex, secteur_id, (dp).geom FROM (
      	SELECT
      		row_number() over() as vertex,
      	    secteur_id,
        		path_seq,
      		ST_DumpPoints(the_geom) AS dp
      	FROM phase_2_trace_pgr
          WHERE secteur_id = $(secteur_id)
      	ORDER BY secteur_id, path_seq
      ) as s
    RESULT -> LineBuilder_2
LineBuilder_2
    ACCUM_INPUT_ATTRS = Use Attributes From One Feature
    GROUP_BY = secteur_id
    REMOVE_DUPLICATES = No
    LINE -> FeatureMerger_2 [REQUESTOR]
0_phase_2_trace_pgr: Inspector [off]
Note: public.secteur
secteur (reader POSTGRES_1)
    attributes: id int4, nom_br text, nom_fr text, objectif_km int4, km_redadeg int4
    -> AttributeRenamer_2
AttributeRenamer_2
    ATTR_TABLE = RENAME_SET_DEFAULT id > secteur_id
    -> FeatureMerger [SUPPLIER]
    -> FeatureMerger_2 [SUPPLIER]
FeatureMerger_2
    ATTR_ACCUM_MODE = Merge Supplier
    ATTR_CONFLICT_RES = Use Requestor
    IGNORE_NULLS = No
    JOIN_KEYS = @Value(secteur_id) @Value(secteur_id) AUTO
    MERGE_TYPE = Attributes Only
    PROCESS_DUPS = NO
    REJECT_NULL_MISSING_KEYS = No
    SUPPLIERS_FIRST = No
    MERGED -> Sorter_4
Sorter_4
    SORT_PARM = secteur_id NUMERIC ASCENDING
    SORTED -> FeatureMerger [REQUESTOR]
    SORTED -> IterativeSnipper
    SORTED -> LineCombiner_Line
FeatureMerger
    ATTR_ACCUM_MODE = Merge Supplier
    ATTR_CONFLICT_RES = Use Requestor
    IGNORE_NULLS = No
    JOIN_KEYS = @Value(secteur_id) @Value(secteur_id) AUTO
    MERGE_TYPE = Attributes Only
    PROCESS_DUPS = NO
    REJECT_NULL_MISSING_KEYS = No
    SUPPLIERS_FIRST = No
    MERGED -> LengthCalculator_2
LengthCalculator_2
    DIM = 2
    LEN_ATTR = km_reels
    MULT = 1
    -> StringFormatter
StringFormatter
    FORMAT = .2f
    SRC_ATTRS = km_reels
    -> Sorter
Sorter
    SORT_PARM = secteur_id NUMERIC ASCENDING
    SORTED -> secteurs
    SORTED -> Aggregator
    SORTED -> ExpressionEvaluator_2
secteurs: Inspector
Aggregator
    ACCUM_ATTRS_NAME = Use Attributes From One Feature
    AGGREGATE_TYPE = Homogeneous Collection (If Possible)
    GROUP_BY = secteur_id
    MODE = Geometry - Assemble One Level
    ORDERED = No
    SEP = ,
    AGGREGATE -> ExpressionEvaluator
ExpressionEvaluator
    ACTION = Create New Attribute
    EXPRESSION = @round(@Length() / 1000,1)
    VAL_ATTR = km_reels
    -> Generalizer
Generalizer
    ALG_TEXT = Douglas (Generalize)
    CLEANING_TOLERANCE = None
    PRESERVE = Yes
    PRESERVE_PATHS = Yes
    TOLERANCE = 10
    -> phase_3_trace_secteurs (writer POSTGIS_2)
phase_3_trace_secteurs (writer POSTGIS_2)
    attributes: secteur_id int2, nom_fr text, nom_br text, km_reels numeric(20,10)
ExpressionEvaluator_2
    ACTION = Create New Attribute
    EXPRESSION = @round(@Length() / 1000,1)
    VAL_ATTR = km_reels
    -> Generalizer_2
Generalizer_2
    ALG_TEXT = Douglas (Generalize)
    CLEANING_TOLERANCE = None
    PRESERVE = Yes
    PRESERVE_PATHS = Yes
    TOLERANCE = 10
    -> phase_3_trace_secteurs.geojson (writer GEOJSON_1)
Note: phase_3_trace_secteurs.geojson
phase_3_trace_secteurs.geojson (writer GEOJSON_1)
    attributes: secteur_id int, nom_fr string, nom_br string, km_reels float
LineCombiner_Line: Inspector
IterativeSnipper
    SNIPMODE = ToLength
    SnipLength = @Value(km_redadeg)
    -> Counter_2
    <Rejected> -> IterativeSnipper__Rejected_
Counter_2
    CNT_ATTR = troncon_id
    DOMAIN = troncon_id
    SCOPE = Local
    START = $(START)
    -> LengthCalculator
LengthCalculator
    DIM = 2
    LEN_ATTR = longueur
    MULT = 1
    -> Sorter_3
Sorter_3
    SORT_PARM = secteur_id NUMERIC ASCENDING troncon_id NUMERIC ASCENDING
    SORTED -> phase_3_trace_troncons (writer POSTGIS_2)
    SORTED -> CoordinateConcatenator
    SORTED -> 2_tronçons
    SORTED -> phase_3_trace_troncons (writer GEOJSON_2)
2_tronçons: Inspector [off]
Note: phase_3_trace_troncons: redadeg@pgrouting [POSTGIS]
phase_3_trace_troncons (writer POSTGIS_2)
    attributes: troncon_id int2, secteur_id int2
Note: phase_3_trace_troncons [GEOJSON]
phase_3_trace_troncons (writer GEOJSON_2)
    attributes: troncon_id int, secteur_id int
CoordinateConcatenator
    COORDINATES_TO_INCLUDE_DIS = Y X
    COORD_ATTR = _coordinates
    COORD_DELIM = |
    ELEMENT_DELIM = ,
    -> AttributeSplitter
AttributeSplitter
    ATTR_NAME = _coordinates
    DELIMITER = |
    DROP_EMPTY_PARTS = No
    LIST_NAME = _coords
    TRIM_OPTION = Both
    -> ListElementCounter
ListElementCounter
    CNT_ATTR = _vertex_count
    LIST_NAME = _coords{}
    -> GeometryRemover
GeometryRemover
    -> ListIndexer
    -> ListIndexer_4
Vertex_debut: Inspector [off]
DuplicateFilter
    INPUT_ORDERED_CHOICE = No
    KEYATTR = y_coords_vertex x_coords_vertex
    UNIQUE -> AttributeRemover_3
    DUPLICATE -> DuplicateFilter_Duplicate
AttributeRemover_3
    LIST_ATTRS = _coords{}
    REMOVE_ATTRS = _coords,path_seq,_vertex_count,_coordinates
    -> PointOnLineOverlayer [POINT]
Note: ici on recroise avec le tracé pour récupérer le noms des voies
PointOnLineOverlayer
    ATTR_ACCUM_MODE = Merge Incoming
    ATTR_CONFLICT_RES = Use Original
    DEAGGREGATE_INPUT = Yes
    OV_ATTR = _overlaps
    TOLERANCE = 1
    POINT -> PointOnAreaOverlayer [POINT]
DuplicateFilter_Duplicate: Inspector [off]
Vertex_fin: Inspector [off]
IterativeSnipper__Rejected_: Inspector
osm_municipalities (reader POSTGIS_1)
    attributes: id serial,PrimaryKey, osm_id int8, type text, admin_level text, name text, name_fr text, name_br text, source_name_br text, admincode text,BTree, postcode text, wikidata text, surf_ha numeric(1000,500), x numeric(1000,500), y numeric(1000,500)
    -> BulkAttributeRenamer
BulkAttributeRenamer
    ATTRCHOICE = All Attributes
    MODE_CHOICE = RENAME
    PATTERN_ACTION_DISP = ADDPREFIX
    REPLACE_STR = municipality_
    -> PointOnAreaOverlayer [AREA]
Note: on croise avec les communes pour récupérer leur noms
PointOnAreaOverlayer
    ATTR_ACCUM_MODE = Merge Incoming
    ATTR_CONFLICT_RES = Use Original
    DEAGGREGATE_INPUT = Yes
    OV_ATTR = _overlaps
    POLYS_FIRST = NO
    POINT -> CoordinateSystemSetter
    POINT -> PointOnAreaOverlayer_Point
AttributeRounder_2
    PLACES = 0
    ROUND_TYPE = Nearest
    SRC_ATTRS = longueur
    -> AttributeRenamer
PointOnAreaOverlayer_Point: Inspector [off]

Bookmark: on extrait les coordonnées du premier vertex
ListIndexer
    INDEX = 0
    LIST_ATTR = _coords{}
    -> AttributeSplitter_2
AttributeSplitter_2
    ATTR_NAME = _coords
    DELIMITER = ,
    DROP_EMPTY_PARTS = No
    LIST_NAME = _coords_vertex
    TRIM_OPTION = Both
    -> ListIndexer_2
ListIndexer_2
    INDEX = 0
    LIST_ATTR = _coords_vertex{}
    PREFIX = x
    -> ListIndexer_3
ListIndexer_3
    INDEX = 1
    LIST_ATTR = _coords_vertex{}
    PREFIX = y
    -> AttributeRemover
AttributeRemover
    LIST_ATTRS = _coords_vertex{}
    REMOVE_ATTRS = _coords_vertex{0},_coords{0},_coordinates
    -> VertexCreator

Bookmark: et oncrée le point
VertexCreator
    MODE_NAME = Add Point
    XVAL = @Value(x_coords_vertex)
    YVAL = @Value(y_coords_vertex)
    -> AttributeCreator
AttributeCreator
    ATTR_TABLE = SET_TO position_vertex = debut
    -> DuplicateFilter
    -> Vertex_debut

Bookmark: on extrait les coordonnées du deuxième vertex
ListIndexer_4
    INDEX = @Value(_vertex_count)-1
    LIST_ATTR = _coords{}
    -> AttributeSplitter_3
AttributeSplitter_3
    ATTR_NAME = _coords
    DELIMITER = ,
    DROP_EMPTY_PARTS = No
    LIST_NAME = _coords_vertex
    TRIM_OPTION = Both
    -> ListIndexer_5
ListIndexer_5
    INDEX = 0
    LIST_ATTR = _coords_vertex{}
    PREFIX = x
    -> ListIndexer_6
ListIndexer_6
    INDEX = 1
    LIST_ATTR = _coords_vertex{}
    PREFIX = y
    -> AttributeRemover_2
AttributeRemover_2
    LIST_ATTRS = _coords_vertex{} _coords{}
    REMOVE_ATTRS = _coords_vertex{0},_coords,_coords{0}
    -> VertexCreator_2

Bookmark: et oncrée le point
VertexCreator_2
    MODE_NAME = Add Point
    XVAL = @Value(x_coords_vertex)
    YVAL = @Value(y_coords_vertex)
    -> AttributeCreator_2
AttributeCreator_2
    ATTR_TABLE = SET_TO position_vertex = fin
    -> Vertex_fin
    -> DuplicateFilter

Bookmark: calcul coordonnées
CoordinateSystemSetter
    COORDSYS = EPSG:2154
    -> CoordinateExtractor
CoordinateExtractor
    IND = 0
    MODE = Specify Coordinate
    X_ATTR = pk_x
    Y_ATTR = pk_y
    -> AttributeRounder
AttributeRounder
    PLACES = 2
    ROUND_TYPE = Nearest
    SRC_ATTRS = pk_y pk_x
    -> AttributeCopier
AttributeCopier
    ATTR_TABLE:
      COPY pk_y > pk_lat
      COPY pk_x > pk_long
    -> AttributeReprojector
AttributeReprojector
    DEST = LL-WGS84
    SOURCE = EPSG:2154
    XATTR = pk_long
    YATTR = pk_lat
    -> AttributeRounder_2

Bookmark: final
AttributeRenamer
    ATTR_TABLE:
      RENAME_SET_DEFAULT municipality_nom > municipality_name_fr
      RENAME_SET_DEFAULT longueur > length_real
      RENAME_SET_DEFAULT km_redadeg > length_theorical
      RENAME_SET_DEFAULT municipality_admincode
    -> Sorter_2
Sorter_2
    SORT_PARM = secteur_id NUMERIC ASCENDING troncon_id NUMERIC ASCENDING
    SORTED -> Counter
Counter
    CNT_ATTR = pk_id
    DOMAIN = pk_id
    SCOPE = Local
    START = $(START)
    -> pk
    -> phase_3_pk_auto (writer POSTGIS_2)
    -> LineBuilder
    -> phase_3_pk_auto (writer GEOJSON_3)
pk: Inspector [off]
phase_3_pk_auto (writer POSTGIS_2)
    attributes: pk_id text, pk_x text, pk_y text, pk_long text, pk_lat text, length_real text, length_theorical text, secteur_id int8, municipality_admincode text, municipality_postcode text, municipality_name_fr text, municipality_name_br text, way_osm_id text, way_highway text, way_type text, way_oneway text, way_ref text, way_name_fr text, way_name_br text
Note: phase_3_pk_auto [GEOJSON]
phase_3_pk_auto (writer GEOJSON_3)
    attributes: pk_id string, pk_x string, pk_y string, pk_long string, pk_lat string, length_real string, length_theorical string, secteur_id int, municipality_admincode string, municipality_postcode string, municipality_name_fr string, municipality_name_br string, way_osm_id string, way_highway string, way_type string, way_oneway string, way_ref string, way_name_fr string, way_name_br string
LineBuilder
    ACCUM_INPUT_ATTRS = Use Attributes From One Feature
    REMOVE_DUPLICATES = No
    LINE -> phase_3_pk_sens_verif (writer POSTGIS_2)
phase_3_pk_sens_verif (writer POSTGIS_2)
    attributes: secteur_id int4

FME custom transformer IterativeSnipper
This transformer can be used to snip a line into shorter lines by specifying a segment length or number of output lines.
Input Ports
    Input
Any feature with line geometry.
    Output Ports
    Output
Line features are output. Number of features depends on User Parameters.
    <Rejected>
Features are rejected if they do not have line geometry. The value INVALID_GEOMETRY_TYPE is stored in the fme_rejection_code attribute.
    Parameters
    Snipping Mode
Shorten to Length: Input line will be iteratively cut into lines of desired length. In this mode, a line will be cut into shorter lines until the length becomes smaller than desired length. The short segment will also be output.
Divide into Number of Lines: Input line will be snipped into a desired number of lines with equal lengths.

Parameters:
- SNIPMODE =
- SnipLength =

Input (input)
    -> GeometryFilter
Note: Filter out all geometries / except lines.
GeometryFilter
    BREAK_AGG = No
    GEOM_PORT_NAMES = Line
    LINE -> LengthCalculator
    <UNFILTERED> -> AttributeCreator
Note: Calculate length / of input line.
LengthCalculator
    DIM = 3
    LEN_ATTR = Iterative_Snipper_length
    MULT = 1
    -> Snip_Mode
Note: Determine Snipping Mode
Snip_Mode: Tester
    BOOL_OP = OR
    TEST_CLAUSE = TEST $(SNIPMODE) = ToNumber
    TEST_MODE = TEST
    PASSED -> ExpressionEvaluator
    FAILED -> ParameterFetcher
AttributeCreator
    ATTR_TABLE = SET_TO fme_rejection_code = INVALID_GEOMETRY_TYPE
    -> <Rejected> (output)
<Rejected> (output)
LoopINPUT (input)
    -> LengthCalculator_2
Note: Calculate length / of input line segment.
LengthCalculator_2
    DIM = 3
    LEN_ATTR = Iterative_Snipper_length
    MULT = 1
    -> Tester
Note: If line's length is less than / or equal to Snipping Distance, / send to Output. If not, snip it.
Tester
    BOOL_OP = OR
    TEST_CLAUSE = TEST @Value(Iterative_Snipper_length) <= @Value(Iterative_Snipper_maxLength)
    TEST_MODE = TEST
    PASSED -> AttributeRemover
    FAILED -> Snipper_3
Note: Cut a segment with length / of snipping distance from / the beginning of the line, / output the segment to the / output port, send the rest of the / line to the looping Output port.
Snipper_3
    ENDLOCATIONATTR = @Value(Iterative_Snipper_maxLength)
    MEASUREMENTTYPE = 3D
    SNIPMODE = Distance (Value)
    STARTLOCATIONATTR = 0
    -> AttributeRemover
    REMNANTS -> LoopINPUT (output)
Note: Clean up attributes
AttributeRemover
    REMOVE_ATTRS = Iterative_Snipper_length,Iterative_Snipper_maxLength
    -> Output (output)
Output (output)
LoopINPUT (output)

Bookmark: Determine Snipping Distance
ExpressionEvaluator
    ACTION = Create New Attribute
    EXPRESSION = @Value(Iterative_Snipper_length)/@double($(SnipLength))
    VAL_ATTR = Iterative_Snipper_maxLength
    -> Tester
ParameterFetcher
    ATTR_LIST = Iterative_Snipper_maxLength {$(SnipLength)}
    -> Tester
