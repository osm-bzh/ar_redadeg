FME workspace export_prefecture_liste_voies.fmw

Parameters:
- DestDataset_CSV2 =

Writers:
- CSV2_1: CSV2 to $(DestDataset_CSV2)

SQLCreator
    DATASET = bed110@redadeg_2021@redadeg
    EXPOSED_ATTRIBUTE_LIST = dpt insee nom pk_id voie_ref voie_nom
    FORMAT = POSTGRES
    POSTGRES_NAMED_CONNECTION = bed110@redadeg_2021@redadeg
    SQL_STATEMENT:
      SELECT
        left(com.insee,2) as dpt,
        com.insee, com.nom,
        pk.pk_id, pk.way_ref as voie_ref,
        CASE
          WHEN way_name_fr IS NULL THEN '(voie non dénommée)'
      	ELSE way_name_fr
        END as voie_nom
      FROM phase_3_pk_auto pk, osm_communes com
      WHERE ST_Intersects(pk.the_geom,com.the_geom)
      ORDER BY pk_id
    RESULT -> ar_redadeg_prefecture (writer CSV2_1)
ar_redadeg_prefecture (writer CSV2_1)
    attributes: dpt string, insee string, nom string, pk_id string, voie_ref string, voie_nom string
