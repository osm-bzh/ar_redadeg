FME workspace phase_5 snap.fmw

Parameters:
- SourceDataset_POSTGIS = redadeg@pgrouting   # Connection
- MAX = 5   # Maximum Distance

Readers:
- POSTGIS_1: POSTGIS from $(SourceDataset_POSTGIS)

Note: public.phase_3_trace_troncons: redadeg@pgrouting [POSTGIS]
phase_3_trace_troncons (reader POSTGIS_1) [off]
    attributes: troncon_id int8,PrimaryKey, secteur_id int4
    -> NeighborFinder [CANDIDATE]
NeighborFinder
    CANDIDATES_FIRST = No
    INSERT_VERTEX = No
    K = 1
    MAX = $(MAX)
    MEASURES_FROM_CANDIDATE = Yes
    MEASURE_TYPE = Continuous
    MODE = Bases and Candidates
    TREAT_POLYGON_AS = Lines
    MATCHED -> NeighborFinder_Matched
NeighborFinder_Matched: Inspector
Note: public.phase_5_pk_umap: redadeg@pgrouting [POSTGIS]
phase_5_pk_umap (reader POSTGIS_1)
    attributes: pk_id int4,PrimaryKey, secteur_id int4
    -> NeighborFinder_2 [BASE]
Note: public.phase_5_pk_ref: redadeg@pgrouting [POSTGIS]
phase_5_pk_ref (reader POSTGIS_1)
    attributes: pk_id int4,PrimaryKey, pk_x numeric(8,1), pk_y numeric(8,1), pk_long numeric(10,8), pk_lat numeric(10,8), length_real numeric(6,2), length_theorical int4, secteur_id int4, municipality_admincode text, municipality_postcode text, municipality_name_fr text, municipality_name_br text, way_osm_id int8, way_highway text, way_type text, way_oneway text, way_ref text, way_name_fr text, way_name_br text
    -> NeighborFinder_2 [CANDIDATE]
NeighborFinder_2
    CANDIDATES_FIRST = No
    GROUP_BY = pk_id
    INSERT_VERTEX = No
    K = 1
    MEASURES_FROM_CANDIDATE = Yes
    MEASURE_TYPE = Continuous
    MODE = Bases and Candidates
    TREAT_POLYGON_AS = Lines
    MATCHED -> NeighborFinder_2_Matched
NeighborFinder_2_Matched: Inspector
