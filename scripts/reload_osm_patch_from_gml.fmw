FME workspace reload_osm_patch_from_gml.fmw

Parameters:
- SourceDataset_GML = /Volumes/ker/mael/Downloads/osm_roads_pgr_patch.gml   # Source Geography Markup Language (GML) File(s)
- SourceDataset_POSTGIS = breizhpolenovo@redadeg   # Connection
- DestDataset_POSTGIS = breizhpolenovo@redadeg   # Connection

Readers:
- GML_1: GML from $(SourceDataset_GML) in EPSG:2154
- POSTGIS_1: POSTGIS from $(SourceDataset_POSTGIS) in EPSG:2154

Writers:
- POSTGIS_2: POSTGIS to $(DestDataset_POSTGIS) in EPSG:2154

osm_roads_pgr_patch (reader GML_1)
    attributes: geometryProperty xml_geometry, id xml_int64, id.xsi_nil xml_boolean, osm_id xml_int64, osm_id.xsi_nil xml_boolean, highway xml_buffer, highway.xsi_nil xml_boolean, type xml_buffer, type.xsi_nil xml_boolean, oneway xml_buffer, oneway.xsi_nil xml_boolean, ref xml_buffer, ref.xsi_nil xml_boolean, name_fr xml_buffer, name_fr.xsi_nil xml_boolean, name_br xml_buffer, name_br.xsi_nil xml_boolean, source xml_int64, source.xsi_nil xml_boolean, target xml_int64, target.xsi_nil xml_boolean, cost xml_real64, cost.xsi_nil xml_boolean, reverse_cost xml_real64, reverse_cost.xsi_nil xml_boolean
    -> osm_roads_pgr_patch
    -> osm_roads_pgr_patch (writer POSTGIS_2)
osm_roads_pgr_patch: Inspector
osm_roads_pgr_patch (writer POSTGIS_2)
    attributes: osm_id int8, highway text, type text, oneway text, ref text, name_fr text, name_br text, source int8, target int8, cost float8, reverse_cost float8
osm_roads_pgr_patch (reader POSTGIS_1) [off]
    attributes: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
